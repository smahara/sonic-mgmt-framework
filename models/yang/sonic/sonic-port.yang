module sonic-port {
	namespace "http://github.com/Azure/sonic-port";
	prefix prt;

	import sonic-common {
		prefix scommon;
	}

	organization
		"SONiC";

	contact
		"SONiC";

	description
		"SONIC VLAN";

	revision 2019-05-15 {
		description
			"Initial revision.";
	}


	container sonic-port {

		container PORT {

			list PORT_LIST {
				key "ifname";

				leaf ifname {
					type string {
						pattern "Ethernet([1-3][0-9]{3}|[1-9][0-9]{2}|[1-9][0-9]|[0-9])" {
							error-message "Invalid interface name";
							error-app-tag interface-name-invalid;
						}
					}
				}

				leaf index {
					type uint16;
					mandatory true;

				}

				leaf speed {
					type uint64 {
						range "1000|10000|25000|40000|50000|100000|400000" {
							error-message "Invalid Ethernet interface speed";
							error-app-tag port-speed-invalid;
						}
					}
				}

				leaf valid_speeds {
					type string;
				}

				leaf alias {
					type string {
					    pattern '[ -~]{0,64}';
					}
				}

				leaf description {
					type string {
					    pattern '[ -~]{0,64}';
					}
				}

				leaf mtu{
					type uint32 {
						range "1312..9216" {
							error-message "Invalid MTU value";
							error-app-tag mtu-invalid;
						}
					}
					default 9100;
				}

				leaf lanes {
					type string;
					mandatory true;
				}

				leaf admin_status {
					type scommon:admin-status;
					default "down";
				}
			}
		}
	}
}
