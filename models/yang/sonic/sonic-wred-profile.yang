module sonic-wred-profile {
    namespace "http://github.com/Azure/sonic-wred-profile";
    prefix wrd;

    organization
        "SONiC";

    contact
        "SONiC";

    description
        "SONIC WRED_PROFILE";

    revision 2019-05-15 {
        description
            "Initial revision.";
    }

    container sonic-wred-profile {
        container WRED_PROFILE {
            list WRED_PROFILE_LIST {
                key "name";

                leaf name{
                    type string;
                }

                leaf yellow_min_threshold {
                    type uint64;
                }

                leaf green_min_threshold {
                    type uint64;
                }

                leaf red_min_threshold {
                    type uint64;
                }

                leaf red_max_threshold {
                    type uint64;
                }

                leaf yellow_max_threshold {
                    type uint64;
                }

                leaf green_max_threshold {
                    type uint64;
                }

                leaf yellow_drop_rate {
                    type uint8 {
                        range "1..100";
                    }
                }

                leaf green_drop_rate {
                    type uint8 {
                        range "1..100";
                    }
                }

                leaf red_drop_rate {
                    type uint8 {
                        range "1..100";
                    }
                }

                leaf ecn {
                    type enumeration {
                        enum ecn_none;
                        enum ecn_green;
                        enum ecn_yellow;
                        enum ecn_red;
                        enum ecn_green_yellow;
                        enum ecn_green_red;
                        enum ecn_yellow_red; 
                        enum ecn_all;
                    }
                }
            }
        }
    }
}
