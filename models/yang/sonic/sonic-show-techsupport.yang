module sonic-show-techsupport {
	namespace "http://github.com/Azure/sonic-show-techsupport";
	prefix sshwtchspt;
    yang-version 1.1;

	import ietf-yang-types {
		prefix yang;
	}

	organization
		"SONiC";

	contact
		"SONiC";

	description
		"SONiC TECH SUPPORT INFORMATION";

	revision 2019-10-15 {
		description
			"Initial revision.";
	}

	rpc sonic-show-techsupport-info {
        input {
            leaf date {
                type yang:date-and-time;
            }
        }
        output {
            leaf output-filename {
                type string;
            }
        }
	}
}
