module sonic-bgp-globals-listen-prefix {
    namespace "http://github.com/Azure/sonic-bgp-globals-listen-prefix";
    prefix sblp;
    yang-version 1.1;

    import sonic-bgp-global {
        prefix sbg;
    }

    import sonic-bgp-peergroup {
        prefix pg;
    }

    import ietf-inet-types {
        prefix inet;
    }

    organization
        "SONiC";

    contact
        "SONiC";

    description
        "SONIC BGP Globals Listen Prefix";

    revision 2019-12-03 {
        description
            "Initial revision.";
    }

    container sonic-bgp-globals-listen-prefix {
        container BGP_GLOBALS_LISTEN_PREFIX {
            list BGP_GLOBALS_LISTEN_PREFIX_LIST {
                key "vrf ip_prefix";

                leaf vrf {
                    type leafref {
                        path "/sbg:sonic-bgp-global/sbg:BGP_GLOBALS/sbg:BGP_GLOBALS_LIST/sbg:vrf";
                    }
                }

                leaf ip_prefix {
                    type inet:ip-prefix;
                }

                leaf peer_group {
                    type leafref {
                        path "/pg:sonic-bgp-peergroup/pg:BGP_PEER_GROUP/pg:BGP_PEER_GROUP_LIST/pg:peer_group_name";
                    }
                }

            }
        }
    }
}
