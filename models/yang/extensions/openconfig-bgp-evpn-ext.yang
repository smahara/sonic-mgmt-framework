module openconfig-bgp-evpn-ext {

  yang-version "1";

  namespace "http://openconfig.net/yang/bgp-evpn/extension";

  prefix "oc-bgp-evpn-ext";

  import openconfig-network-instance { prefix oc-netinst; }
  import openconfig-network-instance-types { prefix "oc-ni-types"; }
  import ietf-routing-types { prefix "ietfrt"; }
  import openconfig-bgp-types { prefix oc-bgp-types; }
  import openconfig-rib-bgp { prefix oc-rib-bgp; }
  import openconfig-bgp-ext { prefix oc-bgp-ext; }
  import openconfig-inet-types { prefix oc-inet; }

  organization "Broadcom";

  contact
  "Broadcom";

  description
  "Model for managing BGP EVPN config.";

  revision 2019-10-03 {
    description
    "Initial augment file.";
  }

  grouping bgp-common-mp-l2vpn-evpn-vni-config {
    description
    "Configuration parameters relating to evpn";

    leaf advertise-default-gw {
      type boolean;
      default "false";
      description
      "If set to true, advertise default gateway";
    }

    leaf route-distinguisher {
      //type oc-ni-types:route-distinguisher;
      type string;
      description
      "The route distinguisher that should be used for the local
      VRF or VSI instance when it is signalled via BGP.";
    }

    uses ietfrt:vpn-route-targets;

  }

  grouping bgp-common-mp-l2vpn-evpn-list {
    description
    "List of VNIs in EVPN";

    list vni {
      key "vni-number";

      description
      "VNI configuration available for the
      EVPN";

      leaf vni-number {
        type leafref {
          path "../config/vni-number";
        }
        description
        "VNI number";
      }

      container config {
        leaf vni-number {
          type uint32 {
            range "1..16777215";
          }
          description
          "VNI number";
        }
        
      }

      container state {

        config false;
        
        leaf vni-number {
          type uint32;
        }

        leaf type {
          type string;
        }

        leaf is-live {
          type boolean;
        }

        leaf route-distinguisher {
          type string;
        }

        leaf originator {
          type string;
        }

        leaf mcast-group {
          type string;
        }

        leaf advertise-gw-mac {
          type boolean;
        }

        leaf-list import-rts {
          type string;
        }

        leaf-list export-rts {
          type string;
        }

      }

      uses bgp-common-mp-l2vpn-evpn-vni-config;

    }//end list
  }

  // augment statements

  augment "/oc-netinst:network-instances/oc-netinst:network-instance/oc-netinst:protocols/oc-netinst:protocol"
  +"/oc-netinst:bgp/oc-netinst:global/oc-netinst:afi-safis/oc-netinst:afi-safi/oc-netinst:l2vpn-evpn" {

    leaf advertise-all-vni {
      type boolean;
      description "Advertise all VNIs";
    }

    leaf-list advertise-list {
      type identityref {
        base oc-bgp-types:AFI_SAFI_TYPE;
      }
      description "AFI,SAFI";
    }

    uses bgp-common-mp-l2vpn-evpn-vni-config;

    container vnis {
      description
      "VNI configuration";
      uses bgp-common-mp-l2vpn-evpn-list;
    }

    container default-originate {
      description "Specify whether to originate default routes";
      leaf ipv4 {
        type boolean;
      }
      leaf ipv6 {
        type boolean;
      }
    }

    leaf autort {
      description "Enable automatic derivation of route-target";
      type enumeration {
        enum rfc8365-compatible;
      }
    }

    /*leaf flooding {
      description "Specify handling of BUM packets";
      type enumeration {
        enum disable;
        enum head-end-replication;
      }
    }*/

    container dup-addr-detection {
      description "Specify duplicate address detection parameters";
      leaf enabled {
        description "Specify whether duplicate address detection is enabled";
        type boolean;
      }
      leaf max-moves {
        description "Specify maximum allowed moves before address declared as duplicate";
        type uint32;
      }
      leaf time {
        description "Dulplicate address detection time";
        type uint32;
      }
      leaf freeze {
        description "Duplicate address detection freeze, time (30-3600) or permanent";
        type union {
          type uint32;
          type string;
        }
      }
    }

  }//end augment

  /*deviation /oc-netinst:network-instances/oc-netinst:network-instance/oc-netinst:protocols/oc-netinst:protocol/oc-netinst:bgp/oc-netinst:global/oc-netinst:afi-safis/oc-netinst:afi-safi/oc-netinst:l2vpn-evpn {
    deviate not-supported;
  }*/

  grouping evpn-loc-rib-key-refs {
    description
      "Key references to support operational state structure for
      the BGP Adj-RIB tables";

    leaf route-distinguisher {
      type leafref {
        path "../state/route-distinguisher";
      }
      description
        "Reference to the route-distinguisher list key";
    }

    leaf prefix {
      type leafref {
        path "../state/prefix";
      }
      description
        "Reference to the prefix list key";
    }

    leaf origin {
      type leafref {
        path "../state/origin";
      }
      description
        "Reference to the origin list key";
    }

    leaf path-id {
      type leafref {
        path "../state/path-id";
      }
      description
        "Reference to the path-id list key";
    }

  }

  grouping evpn-adj-rib-key-refs {
    description
      "Key references to support operational state structure for
      the BGP Adj-RIB tables";

    leaf route-distinguisher {
      type leafref {
        path "../state/route-distinguisher";
      }
      description
        "Reference to the route-distinguisher list key";
    }

    leaf prefix {
      type leafref {
        path "../state/prefix";
      }
      description
        "Reference to the prefix list key";
    }

    leaf path-id {
      type leafref {
        path "../state/path-id";
      }
      description
        "Reference to the path-id list key";
    }

  }


  grouping evpn-adj-rib-common {
    description
      "Common structural grouping for each EVPN adj-RIB table";

    uses oc-rib-bgp:bgp-common-table-attrs-top;

    container routes {
      config false;
      description
        "Enclosing container for list of routes in the routing
        table.";

      list route {
        key "route-distinguisher prefix";

        description
          "List of routes in the table, keyed by the route
          distinguisher and route prefix.";

        uses evpn-adj-rib-key-refs;

        container state {
          description
            "Operational state data for BGP Adj-RIB entries";

          leaf prefix {
            type string;
            description
              "The EVPN prefix string corresponding to the route";
          }

          leaf route-distinguisher {
            type string;
            description
              "Route distinguisher for the prefix";
          }

          uses oc-rib-bgp:bgp-adj-rib-attr-state;
          uses oc-rib-bgp:bgp-adj-rib-common-attr-refs;
          uses oc-rib-bgp:bgp-common-route-annotations-state;
        }

        uses oc-rib-bgp:bgp-unknown-attr-top;

      }
    }
  }

  grouping evpn-adj-rib-in-post {
    description
      "Common structural grouping for the EVPN adj-rib-in
      post-policy table";

    uses oc-rib-bgp:bgp-common-table-attrs-top;

    container routes {
      config false;
      description
        "Enclosing container for list of routes in the routing
        table.";

      list route {
        key "route-distinguisher prefix";

        description
          "List of routes in the table, keyed by the route
          distinguisher and route prefix.";

        uses evpn-adj-rib-key-refs;

        container state {
          description
            "Operational state data for BGP Adj-RIB entries";

          leaf prefix {
            type string;
            description
              "The EVPN prefix string corresponding to the route";
          }

          leaf route-distinguisher {
            type string;
            description
              "Route distinguisher for the prefix";
          }

          uses oc-rib-bgp:bgp-adj-rib-attr-state;
          uses oc-rib-bgp:bgp-adj-rib-common-attr-refs;
          uses oc-rib-bgp:bgp-common-route-annotations-state;
          uses oc-rib-bgp:bgp-adj-rib-in-post-route-annotations-state;
        }

        uses oc-rib-bgp:bgp-unknown-attr-top;
      }
    }
  }

  grouping evpn-loc-rib-top {
    description
      "Top-level grouping for EVPN routing tables";

    container loc-rib {
      config false;
      description
        "Container for the EVPN BGP LOC-RIB data";

      uses oc-rib-bgp:bgp-common-table-attrs-top;

      container routes {
        description
          "Enclosing container for list of routes in the routing
          table.";

        list route {
          key "route-distinguisher prefix origin path-id";

          description
            "List of routes in the table, keyed by the route
            distinguisher and route prefix.";

          uses evpn-loc-rib-key-refs;

          container state {
            description
              "Operational state data for route entries in the
              BGP LOC-RIB";

            leaf prefix {
              type string;
              description
                "The EVPN prefix string corresponding to the route";
            }

            leaf route-distinguisher {
              type string;
              description
                "Route distinguisher for the prefix";
            }

            uses oc-rib-bgp:bgp-loc-rib-common-keys;
            uses oc-rib-bgp:bgp-loc-rib-common-attr-refs;
            uses oc-rib-bgp:bgp-loc-rib-attr-state;
            uses oc-rib-bgp:bgp-common-route-annotations-state;
            uses oc-rib-bgp:bgp-loc-rib-route-annotations-state;

           }

           uses oc-rib-bgp:bgp-unknown-attr-top;

        }
      }
    }
  }

  grouping evpn-adj-rib-top {
    description
      "Top-level grouping for Adj-RIB table";

    container neighbors {
      config false;
      description
        "Enclosing container for neighbor list";

      list neighbor {
        key "neighbor-address";
        description
          "List of neighbors (peers) of the local BGP speaker";

        leaf neighbor-address {
          type leafref {
            path "../state/neighbor-address";
          }
          description
            "Reference to the list key";
        }

        container state {
          description
            "Operational state for each neighbor BGP Adj-RIB";

          leaf neighbor-address {
            type oc-inet:ip-address;
            description
              "IP address of the BGP neighbor or peer";
          }
        }

        container adj-rib-in-pre {
          description
            "Per-neighbor table containing the NLRI updates
            received from the neighbor before any local input
            policy rules or filters have been applied.  This can
            be considered the 'raw' updates from the neighbor.";

          uses evpn-adj-rib-common;

        }

        container adj-rib-in-post {
          description
            "Per-neighbor table containing the paths received from
            the neighbor that are eligible for best-path selection
            after local input policy rules have been applied.";

          uses evpn-adj-rib-in-post;
        }

        container adj-rib-out-pre {
          description
            "Per-neighbor table containing paths eligble for
            sending (advertising) to the neighbor before output
            policy rules have been applied";

          uses evpn-adj-rib-common;

        }

        container adj-rib-out-post {
          description
            "Per-neighbor table containing paths eligble for
            sending (advertising) to the neighbor after output
            policy rules have been applied";

          uses evpn-adj-rib-common;

        }
      }
    }
  }

  augment "/oc-netinst:network-instances/oc-netinst:network-instance/oc-netinst:protocols/oc-netinst:protocol"
  +"/oc-netinst:bgp/oc-netinst:rib/oc-netinst:afi-safis/oc-netinst:afi-safi" {

    container l2vpn-evpn {
      when "../afi-safi-name = 'oc-bgp-types:L2VPN_EVPN'" {
        description
        "Include this container only for the L2VPN AFI, EVPN
        SAFI.";
      }
      description
      "Routing tables for the L2VPN, EVPN SAFI.";

      uses evpn-loc-rib-top;
      //uses evpn-adj-rib-top;

    }
  }//augment

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:loc-rib/oc-bgp-evpn-ext:routes/oc-bgp-evpn-ext:route/oc-bgp-evpn-ext:state/oc-bgp-evpn-ext:attr-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:loc-rib/oc-bgp-evpn-ext:routes/oc-bgp-evpn-ext:route/oc-bgp-evpn-ext:state/oc-bgp-evpn-ext:community-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:loc-rib/oc-bgp-evpn-ext:routes/oc-bgp-evpn-ext:route/oc-bgp-evpn-ext:state/oc-bgp-evpn-ext:ext-community-index {
    deviate not-supported;
  }

  /*deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-in-pre/oc-bgp-evpn-ext:routes/oc-bgp-evpn-ext:route/oc-bgp-evpn-ext:state/oc-bgp-evpn-ext:attr-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-in-pre/oc-bgp-evpn-ext:routes/oc-bgp-evpn-ext:route/oc-bgp-evpn-ext:state/oc-bgp-evpn-ext:community-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-in-pre/oc-bgp-evpn-ext:routes/oc-bgp-evpn-ext:route/oc-bgp-evpn-ext:state/oc-bgp-evpn-ext:ext-community-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-in-post/oc-bgp-evpn-ext:routes/oc-bgp-evpn-ext:route/oc-bgp-evpn-ext:state/oc-bgp-evpn-ext:attr-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-in-post/oc-bgp-evpn-ext:routes/oc-bgp-evpn-ext:route/oc-bgp-evpn-ext:state/oc-bgp-evpn-ext:community-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-in-post/oc-bgp-evpn-ext:routes/oc-bgp-evpn-ext:route/oc-bgp-evpn-ext:state/oc-bgp-evpn-ext:ext-community-index {
    deviate not-supported;
  }


  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-out-pre/oc-bgp-evpn-ext:routes/oc-bgp-evpn-ext:route/oc-bgp-evpn-ext:state/oc-bgp-evpn-ext:attr-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-out-pre/oc-bgp-evpn-ext:routes/oc-bgp-evpn-ext:route/oc-bgp-evpn-ext:state/oc-bgp-evpn-ext:community-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-out-pre/oc-bgp-evpn-ext:routes/oc-bgp-evpn-ext:route/oc-bgp-evpn-ext:state/oc-bgp-evpn-ext:ext-community-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-out-post/oc-bgp-evpn-ext:routes/oc-bgp-evpn-ext:route/oc-bgp-evpn-ext:state/oc-bgp-evpn-ext:attr-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-out-post/oc-bgp-evpn-ext:routes/oc-bgp-evpn-ext:route/oc-bgp-evpn-ext:state/oc-bgp-evpn-ext:community-index {
    deviate not-supported;
  }

  deviation /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-out-post/oc-bgp-evpn-ext:routes/oc-bgp-evpn-ext:route/oc-bgp-evpn-ext:state/oc-bgp-evpn-ext:ext-community-index {
    deviate not-supported;
  }*/

  augment /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:loc-rib/oc-bgp-evpn-ext:routes/oc-bgp-evpn-ext:route {
      uses oc-bgp-ext:bgp-ext-attr-sets;
  }

  /*augment /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-in-pre/oc-bgp-evpn-ext:routes/oc-bgp-evpn-ext:route {
      uses oc-bgp-ext:bgp-ext-attr-sets;
  }
  augment /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-in-post/oc-bgp-evpn-ext:routes/oc-bgp-evpn-ext:route {
      uses oc-bgp-ext:bgp-ext-attr-sets;
  }

  augment /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-out-pre/oc-bgp-evpn-ext:routes/oc-bgp-evpn-ext:route {
      uses oc-bgp-ext:bgp-ext-attr-sets;
  }
  augment /oc-netinst:network-instances/oc-netinst:network-instance/oc-netinst:protocols/oc-netinst:protocol/oc-netinst:bgp/oc-netinst:rib/oc-netinst:afi-safis/oc-netinst:afi-safi/oc-bgp-evpn-ext:l2vpn-evpn/oc-bgp-evpn-ext:neighbors/oc-bgp-evpn-ext:neighbor/oc-bgp-evpn-ext:adj-rib-out-post/oc-bgp-evpn-ext:routes/oc-bgp-evpn-ext:route {
      uses oc-bgp-ext:bgp-ext-attr-sets;
  }*/

}//end module
