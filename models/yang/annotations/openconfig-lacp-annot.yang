module openconfig-lacp-annot {

    yang-version "1";

    namespace "http://openconfig.net/yang/annotation/oc-lacp-annot";
    prefix "oc-lacp-annot";

    import openconfig-interfaces { prefix oc-if; }
    import openconfig-yang-types { prefix oc-yang; }
    import openconfig-extensions { prefix oc-ext; }
    import openconfig-lacp { prefix oc-lacp; }

    deviation /oc-lacp:lacp/oc-lacp:interfaces {
      deviate add {
          sonic-ext:subtree-transformer "lacp_get_xfmr";
      }
    }

}
