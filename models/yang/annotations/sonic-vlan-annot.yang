module sonic-vlan-annot {

    yang-version "1.1";

    namespace "http://openconfig.net/yang/annotation";
    prefix "svlan-annot"; 

    import sonic-vlan { prefix svlan; }


    deviation /svlan:sonic-vlan-state/svlan:VLAN_TABLE  {
      deviate add {
		sonic-ext:db-name "APPL_DB";
      }
    }

    deviation /svlan:sonic-vlan-state/svlan:VLAN_MEMBER_TABLE {
      deviate add {
        sonic-ext:db-name "APPL_DB";
      }
    }
}
