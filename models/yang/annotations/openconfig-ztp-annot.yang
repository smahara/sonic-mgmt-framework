module openconfig-ztp-annot {
   
    yang-version "1";
    namespace "http://openconfig.net/yang/annotation";
    prefix "oc-ztp-annot";

    import sonic-extensions { prefix sonic-ext; }
    import openconfig-ztp { prefix oc-ztp; }
    import openconfig-extensions { prefix oc-ext; }

    deviation /oc-ztp:ztp/oc-ztp:ztp-status {
        deviate add {
            sonic-ext:subtree-transformer "ztp_status_xfmr";
            }
    }
    deviation /oc-ztp:ztp/oc-ztp:ztp-enable {
        deviate add {
            sonic-ext:subtree-transformer "ztp_enable_xfmr";
            }
    }
    deviation /oc-ztp:ztp/oc-ztp:ztp-disable {
        deviate add {
            sonic-ext:subtree-transformer "ztp_disable_xfmr";
            }
    }

}
