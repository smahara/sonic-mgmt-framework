module sonic-common {
    namespace "http://github.com/Azure/sonic-common";
    prefix sv;

    import ietf-yang-types {
        prefix yang;
    }

    organization
        "SONiC";

    contact
        "SONiC";

    description
        "SONIC VLAN";

    revision 2019-05-15 {
        description
            "Initial revision.";
    }

    typedef tagging_mode {
        type enumeration {
            enum untagged;
            enum tagged;
            enum priority_tagged;
        }
    }

    typedef admin-status {
        type enumeration {
            enum up;
            enum down;
        }
    }

    typedef oper-status {
        type enumeration {
            enum up;
            enum down;
        }
    }

    extension custom-handler {
        description
            "Node should be handled by custom handler";
        argument "name";
    }

    extension db-name {
        description
            "DB name, e.g. APPL_DB, CONFIG_DB";
        argument "value";
    }

    extension key-delim {
        description
            "Key delimeter, e.g. - |, :";
        argument "value";
    }

    extension key-pattern {
        description
            "Key pattern, e.g. - ACL_RULE|{aclname}|{rulename}";
        argument "value";
    }

    extension map-list {
        description
            "If it is a map list";
        argument "value"; 
    }

    extension map-leaf {
        description
            "Map leaf names";
        argument "value"; 
    }

    extension pf-check {
        description
            "Platform specific validation";
        argument "handler"; 
    }

    container operation {
        leaf operation {
            type string;
        }
    }
}
