module sonic-extensions {

    yang-version "1";

    // namespace
    namespace "http://openconfig.net/yang/sonic-ext";

    prefix "sonic-ext";

    // meta
    organization "Sonic working group";

    contact
        "OpenConfig working group
        www.openconfig.net";

    description
        "This module provides extensions to the YANG language to allow
        Sonic specific functionality and meta-data to be defined.";

    revision "2019-08-30" {
        description
            "Add extensions for redis DB mappings to identify the Redis DB name.";
    }

    revision "2019-07-26" {
        description
            "Add extensionis for redis DB mappings for table, table-keys, table-fields and corresponding transformer methods.";
    }


    // extension statements
    extension table-name {
        argument "table-name";
        description "Db table name.";
    }

    extension key-transformer {
        argument "key-transformer-name";
        description "Db table key transformer name indicating that the list keys together form db table keys.";
    }

    extension key-delimiter {
        argument "key-delimiter-string";
        description "Db table key values delimiter.";
    }

    extension field-name {
        argument "field-name";
        description "Db table field name.";
    }

    extension field-transformer {
        argument "field-transformer-name";
        description "Db table field transformer name.This can be applied to either transform yang value to some different format
            or choose a specific DB field based on the type of yang value.";
    }

    extension subtree-transformer {
        argument "subtree-transformer-name";
        description "Subtree/node level transformer name that will have db mappings for an entire yang subtree.";
    }

    extension post-transformer {
        argument "post-transformer-name";
        description "Transformer name that will perform post-translation tasks.";
    }

    extension get-validate {
        argument "get-validate-name";
        description "Validation callpoint used to validate a YANG node during data translation back to YANG as a response to GET.";
    }

    extension redis-db-name {
        argument "db-name";
        description "DB name that will indicate where data is stored. Eg: Config DB, App DB etc";
    }
    extension table-transformer {
        argument "table-transformer-name";
        description "Db table transformer name.This can be applied to either transform yang value to some different format
            or choose a specific DB table based on the type.";
    }
}
