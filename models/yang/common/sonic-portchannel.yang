module sonic-portchannel {
    namespace "http://github.com/Azure/sonic-portchannel";
    prefix spc;

    import ietf-yang-types {
        prefix yang;
    }

    import sonic-common {
        prefix scommon;
    }

    import sonic-port {
        prefix prt;
    }

    organization
        "SONiC";

    contact
        "SONiC";

    description
        "SONIC PORTCHANNEL";

    revision 2019-05-15 {
        description
            "Initial revision.";
    }

    container sonic-portchannel {

        list PORTCHANNEL {
            key "name";

            max-elements 3;

            leaf name {
                type string;
            }

            leaf admin_status {
                type scommon:admin-status;
            }

            leaf mtu {
                type uint16;
            }

            leaf min_links {
                type uint8;
            }

            leaf fallback {
                type boolean;
            }
        }

        list PORTCHANNEL_MEMBER { 
            key "name ifname";
            scommon:key-delim "|";
            scommon:key-pattern "PORTCHANNEL|{name}|{ifname}";

            leaf name {
                type leafref {
                    path "../../PORTCHANNEL/name";
                }
            }

            leaf ifname {
                type leafref {
                    path "/prt:sonic-port/prt:PORT/prt:ifname";
                }
            }
        }
    }
}
